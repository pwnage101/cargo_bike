# -*- coding: utf-8 -*-
from FreeCAD import Base
Vec = Base.Vector

import numpy as np
import math

#design_params = App.ActiveDocument.getObjectsByLabel('design_params')[0]
#upcycled_fork = App.ActiveDocument.getObjectsByLabel('upcycled_fork')[0]
ref = App.ActiveDocument.getObjectsByLabel('References')[0]

current_row = 1
def setref(alias, value, units=None, notes=''):
    """
    Set a value for the given alias in the References spreadsheet
    """
    global current_row
    formatted_value = value
    if units:
        formatted_value = '{:.4f} {}'.format(value, units)

    ref.set(
        'A{}'.format(current_row),
        alias
    )
    ref.set(
        'B{}'.format(current_row),
        formatted_value
    )
    ref.set(
        'C{}'.format(current_row),
        notes
    )
    current_row += 1

def degree_to_rad(degree):
    return degree * math.pi/180

def rotation_matrix(axis, theta):
    """
    Return the rotation matrix associated with counterclockwise rotation about
    the given axis by theta radians.
    """
    axis = np.asarray(axis)
    axis = axis/math.sqrt(np.dot(axis, axis))
    a = math.cos(theta/2.0)
    b, c, d = -axis*math.sin(theta/2.0)
    aa, bb, cc, dd = a*a, b*b, c*c, d*d
    bc, ad, ac, ab, bd, cd = b*c, a*d, a*c, a*b, b*d, c*d
    return np.array([[aa+bb-cc-dd, 2*(bc+ad), 2*(bd-ac)],
                     [2*(bc-ad), aa+cc-bb-dd, 2*(cd+ab)],
                     [2*(bd+ac), 2*(cd-ab), aa+dd-bb-cc]])

def rotated_about_axis(vector, axis, theta):
    """
    Rotate the given Vector according to the given axis and theta.

    Returns:
        a new vector
    """
    rotated = np.dot(rotation_matrix(axis, theta), np.asarray(vector))
    return Vec(rotated)

def line_plane_intersection(l, p):
    s = ( p[1].x * p[0].x + p[1].y * p[0].y + p[1].z * p[0].z - p[1].x * l[0].x - p[1].y * l[0].y - p[1].z * l[0].z ) \
        / \
        ( p[1].x * l[1].x + p[1].y * l[1].y + p[1].z * l[1].z )
    return l[0] + Vec(l[1]).multiply(s)

def line_line_intersection(l1, l2):
    """
    Assume the lines intersect in 3D, and do a 2D intersection by selecting the
    two best dimensions out of the three.  Plug the solution back into l1 to
    get the final intersection point in 3D.

    FIXME: UNTESTED
    """
    # point p is perpendicular to both lines
    p = l1[1].cross(l2[1])
    p0 = math.fabs(p[0])
    p1 = math.fabs(p[1])
    p2 = math.fabs(p[2])
    axisA = 0
    axisB = 1
    if p0 > p1 and p0 > p2:
        axisA = 1
        axisB = 2
    elif p1 > p0 and p1 > p2:
        axisA = 0
        axisB = 2
    l1_parameter = \
        (l2[1][axisA] * l2[0][axisB] - l2[1][axisA] * l1[0][axisB] + l2[1][axisB] * l1[0][axisA] - l2[1][axisB] * l2[0][axisA]) \
            / \
        (l2[1][axisA] * l1[1][axisB] - l2[1][axisB] * l1[1][axisA])
    # plugging back into the l1 parametric line equation
    intersection = l1[0] + Vec(l1[1]).multiply(l1_parameter)
    return intersection

def pos_along_axis(point, axis):
    """
    Parameters:
        point (Vector): point in question.
        axis (two tuple of Vectors): position and direction of axis.

    Returns:
        float: position along the axis where the point, or its perpendicular
            projection, lies.
    """
    return point.sub(axis[0]).dot(axis[1])

def point_along_axis(pos, axis):
    """
    Parameters:
        pos (float): position along axis
        axis (two tuple of Vectors): position and direction of axis

    Returns:
        Vector: point which corresponds to the given position along the given
            axis.
    """
    return Vec(axis[1]).multiply(pos).add(axis[0])


class Cope(object):
    def __init__(self, tube_pos, tube_centerline, tube_diameter):
        self.tube_pos = tube_pos
        self.tube_centerline = tube_centerline
        self.tube_centerline.normalize()
        self.tube_diameter = tube_diameter

    def get_tube_centerline_facing_away(self):
        raise(NotImplementedError)

    def angle_vector(self):
        raise(NotImplementedError)

    def angle(self, first_cope):
        """
        Returns:
            float: angle (rad) between first cope angle vector and this one's.
        """
        small_angle = first_cope.angle_vector().getAngle(self.angle_vector())
        if first_cope.get_tube_centerline_facing_away().dot(self.angle_vector().cross(first_cope.angle_vector())) > 0:
            return small_angle
        else:
            return 0 - small_angle

    def angle_along_circumference(self, first_cope):
        """
        Returns:
            float: distance (mm) from reference angle to this angle.
        """
        angle = self.angle(first_cope)
        circumference = self.tube_diameter * math.pi
        distance_along_circumference = circumference * angle / (2 * math.pi)
        return distance_along_circumference

    def center(self):
        raise(NotImplementedError)

    def closest_point(self, points):
        distance_map = [
            (point, self.center().distanceToPoint(point))
            for point in points
        ]
        closest = None
        for point, distance in distance_map:
            if not closest or distance < closest[1]:
                closest = (point, distance)
        return closest[0]


class FlatCope(Cope):
    # according to the central machinery bandsaw manual
    MAX_BANDSAW_ANGLE = degree_to_rad(45)

    def __init__(self, tube_pos, tube_centerline, tube_diameter, cut_face_pos, cut_face_normal):
        """
        Parameters:
            tube_centerline (Vec): normalized vector representing the
                centerline of the tubing.
            cut_face_normal (Vec): normal vector of the cut face.
        """
        super(FlatCope, self).__init__(tube_pos, tube_centerline, tube_diameter)
        self.cut_face_pos = cut_face_pos
        self.cut_face_normal = cut_face_normal
        self.cut_face_normal.normalize()

    def center(self):
        return line_plane_intersection(
            (self.tube_pos, self.tube_centerline),
            (self.cut_face_pos, self.cut_face_normal),
        )

    def get_tube_centerline_facing_away(self):
        if self.tube_centerline.dot(self.cut_face_normal) < 0:
            return self.tube_centerline.negative()
        else:
            return self.tube_centerline

    def angle_vector(self):
        tube_centerline_facing_away = self.get_tube_centerline_facing_away()
        return tube_centerline_facing_away.cross(self.cut_face_normal)

    def _pos_relative(self, reference_axis):
        return pos_along_axis(self.center(), reference_axis)

    def _bandsaw_angle(self):
        """
        Get a cut angle which would be indicated on a horizontal metal bandsaw.
        """
        return self.get_tube_centerline_facing_away().getAngle(self.cut_face_normal)

    def _bandsaw_angle_notes(self):
        msg = ''
        if self._bandsaw_angle() > self.MAX_BANDSAW_ANGLE:
            msg = 'angle beyond machine limits'
        return msg

    def set_references(self, prefix, reference_zero_cope, reference_axis):
        setref('{}.tool'.format(prefix), "bandsaw")
        setref('{}.angle'.format(prefix), self.angle(reference_zero_cope), 'rad')
        setref('{}.angle_along_circumference'.format(prefix), self.angle_along_circumference(reference_zero_cope), 'mm')
        setref('{}.pos'.format(prefix), self._pos_relative(reference_axis), 'mm')
        setref('{}.bandsaw_angle'.format(prefix),   self._bandsaw_angle(), 'rad', notes=self._bandsaw_angle_notes())


class CylindricalCope(Cope):
    # according to the central machinery notching jig manual
    MAX_HOLESAW_ANGLE = degree_to_rad(60)

    def __init__(self, tube_pos, tube_centerline, tube_diameter, cope_pos, cope_diameter, saw_direction):
        """
        Parameters:
            tube_centerline (Vec): normalized vector representing the
                centerline of the tubing.
            saw_direction (Vec): axis of saw rotation, pointing in direction
                of cutting motion.
        """
        super(CylindricalCope, self).__init__(tube_pos, tube_centerline, tube_diameter)
        self.cope_pos = cope_pos
        self.cope_diameter = cope_diameter
        self.saw_direction = saw_direction
        self.saw_direction.normalize()

    def center(self):
        return line_line_intersection(
            (self.tube_pos, self.tube_centerline),
            (self.cope_pos, self.saw_direction),
        )

    def get_tube_centerline_facing_away(self):
        if self.tube_centerline.dot(self.saw_direction.negative()) < 0:
            return self.tube_centerline.negative()
        else:
            return self.tube_centerline

    def angle_vector(self):
        tube_centerline_facing_away = self.get_tube_centerline_facing_away()
        return tube_centerline_facing_away.cross(self.saw_direction.negative()).cross(tube_centerline_facing_away)

    def _pos_relative(self, reference_axis):
        return pos_along_axis(self.center(), reference_axis)

    def _holesaw_angle(self):
        """
        Get a cut angle which would be indicated on a tubing notcher jig.
        """
        return self.saw_direction.getAngle(self.get_tube_centerline_facing_away()) - (math.pi/2)

    def _holesaw_angle_notes(self):
        msg = ''
        if self._holesaw_angle() > self.MAX_HOLESAW_ANGLE:
            msg = 'angle beyond machine limits'
        return msg

    def _holesaw_following_pos(self, reference_axis):
        cope_offset = self.cope_diameter / (2 * math.cos(self._holesaw_angle()))
        tube_offset = self.tube_diameter / (2 * math.cos(self._holesaw_angle()))
        holesaw_following_touch_point_relative = \
            Vec(self.get_tube_centerline_facing_away()).negative().multiply(cope_offset).add(
                Vec(self.saw_direction).negative().multiply(tube_offset)
            )
        holesaw_following_touch_point = self.center().add(holesaw_following_touch_point_relative)
        return pos_along_axis(holesaw_following_touch_point, reference_axis)

    def set_references(self, prefix, reference_zero_cope, reference_axis):
        setref('{}.tool'.format(prefix), "holesaw")
        setref('{}.angle'.format(prefix), self.angle(reference_zero_cope), 'rad')
        setref('{}.angle_along_circumference'.format(prefix), self.angle_along_circumference(reference_zero_cope), 'mm')
        setref('{}.pos'.format(prefix), self._pos_relative(reference_axis), 'mm')
        setref('{}.holesaw_angle'.format(prefix), self._holesaw_angle(), 'rad', notes=self._holesaw_angle_notes())
        setref('{}.holesaw_following_pos'.format(prefix), self._holesaw_following_pos(reference_axis), 'mm')
        setref('{}.holesaw_diameter'.format(prefix), self.cope_diameter, 'mm')


class CopedTubing(object):
    def __init__(self, name, part_object, shell_face_num=0, cope_faces=[]):
        self._perpendicular_bounds = None
        self._reference_axis = None
        self.name = name
        self.part_object = part_object
        self.shell_face_num = shell_face_num
        self.copes = []
        self.add_copes_from_faces(cope_faces)

    @property
    def shell_face(self):
        return self.part_object.Shape.Faces[self.shell_face_num]

    @property
    def center_of_tube_stock(self):
        a, b = self.perpendicular_bounds
        return Vec(a.add(b)).multiply(0.5)

    @property
    def position(self):
        return self.shell_face.Surface.Center

    @property
    def centerline(self):
        return self.shell_face.Surface.Axis

    @property
    def diameter(self):
        return 2 * self.shell_face.Surface.Radius

    @property
    def arbitrary_reference_axis(self):
        return (self.position, self.centerline)

    @property
    def reference_axis(self):
        if self._reference_axis:
            return self._reference_axis
        reference_cope = self.copes[0]
        bounds = self.perpendicular_bounds
        reference_point = reference_cope.closest_point(bounds)
        reference_direction = reference_cope.get_tube_centerline_facing_away().negative()
        self._reference_axis = (reference_point, reference_direction)
        return self._reference_axis

    @property
    def perpendicular_bounds(self):
        """
        Returns:
            two-tuple of vectors: points along the center axis of the tube
                where bandsaw cuts can be made to form the stock tube.
        """
        if self._perpendicular_bounds:
            return self._perpendicular_bounds
        # use a precision of 0.1mm
        verticies, triangles = self.part_object.Shape.tessellate(0.1)
        pos_min = None
        pos_max = None
        first_iteration = True
        for v in verticies:
            pos = pos_along_axis(v, self.arbitrary_reference_axis)
            if first_iteration:
                first_iteration = False
                pos_min = pos
                pos_max = pos
            elif pos < pos_min:
                pos_min = pos
            elif pos > pos_max:
                pos_max = pos
        bounds = [
            point_along_axis(pos, self.arbitrary_reference_axis)
            for pos
            in (pos_min, pos_max)
        ]
        self._perpendicular_bounds = tuple(bounds)
        return self._perpendicular_bounds

    def add_cope(self, cope, is_reference=False):
        if is_reference:
            self.copes.insert(0, cope)
        else:
            self.copes.append(cope)

    def add_copes_from_faces(self, face_objects):
        for face in face_objects:
            if isinstance(face.Surface, Part.Plane):
                self.add_flat_cope_from_face(face)
            elif isinstance(face.Surface, Part.Cylinder):
                self.add_cylindrical_cope_from_face(face)

    def add_flat_cope(self, cut_pos, cut_face_normal, is_reference=False):
        new_cope = FlatCope(self.position, self.centerline, self.diameter, cut_pos, cut_face_normal)
        self.add_cope(new_cope, is_reference)

    def add_flat_cope_from_face(self, face_object, is_reference=False):
        self.add_flat_cope(face_object.Surface.Position, face_object.Surface.Axis, is_reference)

    def add_cylindrical_cope(self, cope_position, cope_diameter, saw_direction, is_reference=False):
        new_cope = CylindricalCope(self.position, self.centerline, self.diameter, cope_position, cope_diameter, saw_direction)
        self.add_cope(new_cope, is_reference)

    def add_cylindrical_cope_from_face(self, face_object, is_reference=False):
        saw_position = face_object.Surface.Center
        saw_axis = face_object.Surface.Axis
        cope_center = line_line_intersection(
            (self.center_of_tube_stock, self.centerline),
            (face_object.Surface.Center, face_object.Surface.Axis),
        )
        towards_center = self.center_of_tube_stock.sub(cope_center)
        if saw_axis.dot(towards_center) >= 0:
            saw_direction = saw_axis
        else:
            saw_direction = saw_axis.negative()
        self.add_cylindrical_cope(
            saw_position,
            2 * face_object.Surface.Radius,
            saw_direction,
            is_reference
        )

    def set_references(self):
        setref(
            '{}.stock_length'.format(self.name),
            self.perpendicular_bounds[0].distanceToPoint(self.perpendicular_bounds[1]),
            'mm',
        )
        setref(
            '{}.stock_diameter'.format(self.name),
            self.diameter,
            'mm',
        )
        cope_idx = 0
        for cope in self.copes:
            cope_name = '{}.cope_{}'.format(self.name, cope_idx)
            cope.set_references(cope_name, self.copes[0], self.reference_axis)
            cope_idx += 1



###
# Calculating the copes for the lower_down_tube
###
tube_part = App.ActiveDocument.getObjectsByLabel('lower_down_tube')[0]
tube = CopedTubing(
    'lower_down_tube',
    tube_part,
    cope_faces=[
        # cope to cargo_rear_tube
        tube_part.Shape.Faces[6],
        # cope to rear_head_tube
        tube_part.Shape.Faces[5],
    ],
)
tube.set_references()

###
# Calculating the copes for the cargo_side_tube_r
###
tube_part = App.ActiveDocument.getObjectsByLabel('cargo_side_tube_r')[0]
tube = CopedTubing(
    'cargo_side_tube_r',
    tube_part,
    cope_faces=[
        # cope to the cargo_rear_tube
        tube_part.Shape.Faces[2],
    ],
)
tube.set_references()

###
# Calculating the copes for the cargo_front_tube_r
###
tube_part = App.ActiveDocument.getObjectsByLabel('cargo_front_tube_r')[0]
tube = CopedTubing(
    'cargo_front_tube_r',
    tube_part,
    cope_faces=[
        # front tube / side tube joint
        tube_part.Shape.Faces[1],
        # joint with cargo_nose_tube
        tube_part.Shape.Faces[3],
    ],
)
tube.set_references()

###
# Calculating the copes for the cargo_front_tube_l
###
tube_part = App.ActiveDocument.getObjectsByLabel('cargo_front_tube_l')[0]
tube = CopedTubing(
    'cargo_front_tube_l',
    tube_part,
    cope_faces=[
        # front tube / side tube joint
        tube_part.Shape.Faces[1],
        # joint with cargo_nose_tube
        tube_part.Shape.Faces[3],
    ],
)
tube.set_references()

###
# Calculating the copes for the cargo_nose_tube
###
tube_part = App.ActiveDocument.getObjectsByLabel('cargo_nose_tube')[0]
tube = CopedTubing(
    'cargo_nose_tube',
    tube_part,
)
tube.set_references()

###
# Calculating the copes for the front_head_tube
###
tube_part = App.ActiveDocument.getObjectsByLabel('front_head_tube')[0]
tube = CopedTubing(
    'front_head_tube',
    tube_part,
)
tube.set_references()

ref.recompute()

# vim: ft=python
