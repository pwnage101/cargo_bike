# -*- coding: utf-8 -*-
# WARNING: this doesn't actually work, just a WIP

import FreeCAD
import FreeCADGui

__objs__=[]
__objs__.append(FreeCAD.getDocument("cargo_bike").getObjectsByLabel("full_side_full"))
__objs__.append(FreeCAD.getDocument("cargo_bike").getObjectsByLabel("full_side_steerer"))
__objs__.append(FreeCAD.getDocument("cargo_bike").getObjectsByLabel("full_side_fork"))
FreeCADGui.export(__objs__,u"/home/user/workspace/all.pdf")
